(defun c:ChangePropertiesOfEntities (/ ss color layer ltype ent entdata)
  (setq ss (ssget))
  (if ss
    (progn
      (setq color (getint "\nEnter color index (1-255): "))
      (setq layer (getstring "\nEnter new layer name: "))
      (setq ltype (getstring "\nEnter new line type: "))
      (if (and color (>= color 1) (<= color 255))
        (progn
          (repeat (sslength ss)
            (setq ent (ssname ss 0))
            (setq entdata (entget ent))
            (if (assoc 62 entdata)
              (setq entdata (subst (cons 62 color) (assoc 62 entdata) entdata))
              (setq entdata (append entdata (list (cons 62 color))))
            )
            (if (assoc 8 entdata)
              (setq entdata (subst (cons 8 layer) (assoc 8 entdata) entdata))
              (setq entdata (append entdata (list (cons 8 layer))))
            )
            (if (assoc 6 entdata)
              (setq entdata (subst (cons 6 ltype) (assoc 6 entdata) entdata))
              (setq entdata (append entdata (list (cons 6 ltype))))
            )
            (entmod entdata)
            (ssdel ent ss)
          )
        )
        (prompt "\nInvalid color index. Please enter a value between 1 and 255.")
      )
    )
    (prompt "\nNo entities selected.")
  )
  (princ)
)
(princ "\nChangePropertiesOfEntities function loaded. Type ChangePropertiesOfEntities to run.")




(defun C:SPIRAL ( / center radius rinc delta points direction distprompts distances angoffset FULLCIRCLE cmdecho_store)
  (setq FULLCIRCLE (* 2 pi))
  (setq center (getpoint "Center of spiral: "))
  (setq distprompts '("\nInitial spiral radius: " "\nRadius increment per full rotation: " "\nLinear distance between consecutive points: ") distances nil)
  (while distprompts
    (initget 7)
    (setq distances (cons (getdist (car distprompts)) distances) distprompts (cdr distprompts))
  )
  (setq radius (caddr distances) rinc (cadr distances) delta (car distances))
  (initget 7)
  (setq points (getint "\nNumber of points on the spiral: "))
  (initget 1 "Clockwise counteRclockwise")
  (setq direction (getkword "\nSpiral direction (Clockwise counteRclockwise): "))
  (setq cmdecho_store (getvar "CMDECHO"))
  (setvar "CMDECHO" 0)
  (setvar "PDMODE" 33)
  (setq ang 0)
  (while (/= points 0)
    (command "point" (polar center ang radius))
    (setq angoffset (/ delta radius) ang (if (= direction "Clockwise") (- ang angoffset) (+ ang angoffset)))
    (if (< ang 0) (setq ang (+ ang FULLCIRCLE)))
    (if (>= ang FULLCIRCLE) (setq ang (- ang FULLCIRCLE)))
    (setq radius (+ radius (* rinc (/ angoffset FULLCIRCLE))) points (1- points))
  )
  (setvar "CMDECHO" cmdecho_store)
  (princ)
)
